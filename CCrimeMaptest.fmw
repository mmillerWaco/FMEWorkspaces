FME workspace CCrimeMaptest.fmw

Parameters:
- SourceDataset_MSSQL_ADO_3 = PDTiburon   # SQL Server Connection
- SourceDataset_MSSQL_ADO = PDTiburon   # SQL Server Connection
- SourceDataset_CSV2 = C:\Users\mmiller\OneDrive - City of Waco Texas\Documents\2021\Crime Dashboard\locationlist.csv   # Source CSV (Comma Separated Value) File(s)
- SourceDataset_MSSQL_SPATIAL = NTGIS   # SQL Server Connection
- SourceDataset_XLSXR = C:\Users\mmiller\OneDrive - City of Waco Texas\Documents\2021\Crime Dashboard\codeList.xlsx   # Source Microsoft Excel File(s)

Readers:
- MSSQL_ADO_1: MSSQL_ADO from $(SourceDataset_MSSQL_ADO_3)
- MSSQL_ADO_2: MSSQL_ADO from $(SourceDataset_MSSQL_ADO)
- CSV2_1: CSV2 from $(SourceDataset_CSV2)
- MSSQL_SPATIAL_2: MSSQL_SPATIAL from $(SourceDataset_MSSQL_SPATIAL)
- XLSXR_1: XLSXR from $(SourceDataset_XLSXR)
- ARCGISONLINEFEATURES_1: ARCGISONLINEFEATURES

Writers:
- ARCGISONLINEFEATURES_2: ARCGISONLINEFEATURES to <Unused>

PARSMaster_VIEW (reader MSSQL_ADO_1)
    attributes: MAST_REL varchar(20), Agency varchar(4), Report_No varchar(12), Supplement_No varchar(4), Reported_Date datetime, Reported_Time numeric(6,0), CAD_Call_No varchar(11), Status varchar(4), Rpt_Incident_Typ varchar(25), CAD_Call_Type varchar(25), Special_Event_Code varchar(15), Location varchar(60), City varchar(13), ZIP_Code varchar(10), Rep_Dist varchar(6), Area varchar(4), Map_Coordinates varchar(20), Beat varchar(4), From_Date datetime, From_Time numeric(6,0), To_Date datetime, To_Time numeric(6,0), Primary_Unit varchar(6), Member varchar(9), Assignment varchar(4), 2nd_Member varchar(9), 2nd_Assignment varchar(4), Entered_By varchar(9), Assignment2 varchar(4), Staff_Review_ID varchar(9),
      RC_Status varchar(2), RC_Status_Date datetime, RC_Status_Time numeric(6,0), Confidential varchar(1), Conf_Wrk_Group varchar(6), RMS_Transfer varchar(1), Jail_Transfer varchar(1), Prop_Trans_Stat varchar(1), Fast_Track varchar(1), Property varchar(1), CF_Transfer varchar(4), Report_Title varchar(20), Solvability varchar(1), Score numeric(4,0), MUPS_Trans_Stat varchar(1), NIBRS varchar(60), Weather nvarchar(10), Other varchar(17), Language_Translator varchar(15), Neighborhood varchar(10), Gang_Crime varchar(1), Hate_Crime varchar(1), Family_violence varchar(1), Foster_Care_Facility varchar(1), Mental_Illness varchar(1), Metal_Theft varchar(1), Offense_County varchar(15), UCR_Clearance_Code varchar(3), Contact_Complaint_Date datetime, Unable_to_Contact_Date datetime,
      Contact_Witness_Date datetime, Supplement_Action_Date datetime, Supplement_Shift_1 varchar(1), Supplement_Shift_2 varchar(1), Vehicle_Towed_By varchar(1), Vehicle_VIN_Indicator varchar(1)
    -> AttributeFilter
AttributeFilter
    ATTR_NAME = Supplement_No
    ATTR_VALUES = <Empty>,<Missing>,<Null>,<Unfiltered>,0000
    <EMPTY> -> Inspector_2
    <MISSING> -> Inspector_2
    <NULL> -> Inspector_2
    <UNFILTERED> -> Inspector_2
    0000 -> DateTimeConverter_2
Inspector_2
DateTimeConverter_2
    DATETIME_ATTR = Reported_Date
    IN_FORMAT = %Y%m%d%H%M%S
    OUT_FORMAT = %Y-%m-%d
    PASSTHROUGH = NO
    REPAIR_INPUT = YES
    TEST_INPUT = 19980627000000
    -> DateTimeConverter
DateTimeConverter
    DATETIME_ATTR = Reported_Time
    IN_FORMAT = %H%M%S
    OUT_FORMAT = %H:%M
    PASSTHROUGH = NO
    REPAIR_INPUT = YES
    TEST_INPUT = 122800
    -> AddTodayDate
AddTodayDate: DateTimeStamper
    DATETIME_ATTR = _todaytimedate
    INCLUDE_OFFSET = NO
    STAMP_TYPE = datetime
    TIMEZONE = utc
    -> Subtract-X-Date
Subtract-X-Date: DateTimeCalculator
    MODE = DATETIMECALC_1_ADD_INTERVAL
    OPERATION_PARAMETERS = START_DATETIME]@Value(_todaytimedate)]OPERATOR]SUBTRACT]YEARS]1]MONTHS]0]DAYS]0]HOURS]0]MINUTES]0]SECONDS]0]RESULT_DATETIME]_oneyearfromtoday]FME_CONTROLLER_QUERY_FILE]transformers/dependencies/datetimecalculator/DATETIMECALC_1_ADD_INTERVAL.fme]FME_CONTROLLER_CHOICE]DATETIMECALC_1_ADD_INTERVAL
    -> CompareDates
CompareDates: Tester
    BOOL_OP = OR
    TEST_CLAUSE = DATETIME_TEST @Value(Reported_Date) >= @Value(_oneyearfromtoday)
    TEST_MODE = DATETIME_TEST
    PASSED -> Join_ParsInibro [REQUESTOR]
INIBRO_VIEW (reader MSSQL_ADO_2)
    attributes: Report_No varchar(12), Sequence_No varchar(2), Offense varchar(3), Attempt_Complete varchar(1), Offender_Used varchar(5), Bias_Motivation varchar(14), Location_Type varchar(2), Premises varchar(2), Method_of_Entry varchar(1), Criminal_or_Gang varchar(5), Weapon_Type varchar(11), Cargo varchar(1), Nibrs varchar(13), ORI varchar(9), Control varchar(19), INIBRO_ID numeric(18,0)
    -> Join_ParsInibro [SUPPLIER]
Join_ParsInibro: FeatureMerger
    ATTR_ACCUM_MODE = Merge Supplier
    ATTR_CONFLICT_RES = Use Requestor
    IGNORE_NULLS = No
    JOIN_KEYS = @Value(Report_No) @Value(Report_No) AUTO
    MERGE_TYPE = Attributes Only
    PROCESS_DUPS = NO
    REJECT_NULL_MISSING_KEYS = No
    SUPPLIERS_FIRST = No
    MERGED -> Add_Code_Title_and_Definition [REQUESTOR]
codeList (reader XLSXR_1)
    attributes: Code char(5), Offense char(26), Offense Against char(21), Definition char(508)
    -> Add_Code_Title_and_Definition [SUPPLIER]
Add_Code_Title_and_Definition: FeatureMerger
    ATTR_ACCUM_MODE = Prefix Supplier
    IGNORE_NULLS = No
    JOIN_KEYS = @Value(Offense) @Value(Code) STRING
    MERGE_TYPE = Attributes Only
    PROCESS_DUPS = NO
    REJECT_NULL_MISSING_KEYS = No
    SUPPLIERS_FIRST = No
    SUPPLIER_PREFIX = code_
    MERGED -> FeatureMerger_3 [REQUESTOR]
CSV (reader CSV2_1)
    attributes: LocCode uint32, LocationName varchar(35)
    -> FeatureMerger_3 [SUPPLIER]
FeatureMerger_3
    ATTR_ACCUM_MODE = Merge Supplier
    ATTR_CONFLICT_RES = Use Requestor
    IGNORE_NULLS = No
    JOIN_KEYS = @Value(Location_Type) @Value(LocCode) AUTO
    MERGE_TYPE = Attributes Only
    PROCESS_DUPS = NO
    REJECT_NULL_MISSING_KEYS = No
    SUPPLIERS_FIRST = No
    MERGED -> ChangeDetector [REVISED]
ReportsLayer (reader ARCGISONLINEFEATURES_1)
    attributes: OBJECTID OID, Report_No String(12), Reported_Date Date, REV_Street String(100), REV_City String(40), REV_ZIP String(10), REV_Match_addr String(120), ToD String(255), OffenseCommitted String(255), OffenseDef String(512), OffenseAgainst String(512), LocationType String(512), Neighborhood String(40), CouncilDistrict String(43), GlobalID GlobalID(38)
    -> ChangeDetector [ORIGINAL]
ChangeDetector
    BLANK_AND_MISSING_DIFFER = No
    CHECK_TYPES_AND_ENCODINGS = No
    MATCHATTRS = Report_No
    MATCH_STRATEGY = Match Selected Attributes
    UNCHANGED_OUTPUT = Output Original
    UPSERT_MODE = No
    INSERTED -> StringSearcher_3
StringSearcher_3
    CASE = no
    MATCHED_RESULT_ATTR = _first_match
    REGEXP = ^.*?\/.*?$
    STRING_TO_SEARCH = @Value(Location)
    MATCHED -> Geocoder_2
    NOT_MATCHED -> StringSearcher_2
StringSearcher_2
    CASE = no
    MATCHED_RESULT_ATTR = _first_match
    REGEXP = ^[a-z] (\d+[a-z]+)
    STRING_TO_SEARCH = @Value(Location)
    MATCHED -> Geocoder_2
    NOT_MATCHED -> StringSearcher
StringSearcher
    CASE = no
    MATCHED_RESULT_ATTR = _first_match
    REGEXP = (\d+)
    STRING_TO_SEARCH = @Value(Location)
    MATCHED -> AttributeManager
AttributeManager
    ATTR_TABLE:
      SET_TO Address_Anon = FME_CONDITIONAL:DEFAULT_VALUE'_FME_NO_OP_'BOOL_OP;OR;COMPOSITE_TEST;1;TEST @StringLength(@Value(_first_match)) = 4'@Left(@Value(_first_match),2)00'BOOL_OP;OR;COMPOSITE_TEST;1;TEST @StringLength(@Value(_first_match)) = 3'@Left(@Value(_first_match),1)00'BOOL_OP;OR;COMPOSITE_TEST;1;TEST @StringLength(@Value(_first_match)) = 2'0'BOOL_OP;OR;COMPOSITE_TEST;1;TEST @StringLength(@Value(_first_match)) = 1'0'FME_NUM_CONDITIONS5___
      REMOVE code_Code
      RENAME_SET_VALUE code_Offense > OffenseCommitted
      RENAME_SET_VALUE code_Offense Against > OffenseAgainst
      RENAME_SET_VALUE code_Definition > OffenseDef
    -> StringReplacer_2
StringReplacer_2
    CASE = NO
    FIND_TEXT = @Value(_first_match)
    NO_MATCH = _FME_NO_OP_
    REGEXP = NO
    REPLACE_TEXT = @Value(Address_Anon)
    SRC_ATTRS = Location
    -> Geocoder_2
Geocoder_2
    GEOCODING_SERVICE = ArcGIS Server
    RETURN_JSON_RESPONSE = no
    THREADS = 4
    TIMEOUT = 60
    VERIFY_HTTPS = yes
    -> SpatialRelator [Requestor]
    -> Geocoder_2_Output
    <REJECTED> -> Geocoder_2_Output
    <REJECTED> -> Geocoder_2__Rejected_
Geocoder_2_Output: Inspector
Geocoder_2__Rejected_: Inspector
NEIGHBORHOODS (reader MSSQL_SPATIAL_2)
    attributes: OBJECTID integer, CITY varchar(20), NBRHOOD_ID integer, NAME varchar(40), COLOR smallint, INSPECTOR varchar(35), ACTIVE varchar(15), DIST1 varchar(2), Rotation smallint, Scale numeric(38,8), GDB_GEOMATTR_DATA varbinary_max, PresidentName nvarchar(50), Contact nvarchar(50), ContactInfo nvarchar(50), Notes nvarchar(100)
    -> SpatialRelator [Supplier]
SpatialRelator
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = WITHIN INTERSECTS
    SUCCESS_ATTR = _nsupp
    -> AttributeManager_2
AttributeManager_2
    ATTR_TABLE:
      REMOVE Map_Coordinates
      REMOVE _todaytimedate
      REMOVE _oneyearfromtoday
      REMOVE _first_match
      REMOVE Address_Anon
      REMOVE OBJECTID
      REMOVE CITY
      REMOVE NBRHOOD_ID
      RENAME_SET_VALUE NAME > Neighborhood
      REMOVE COLOR
      REMOVE INSPECTOR
      REMOVE ACTIVE
      REMOVE DIST1
      REMOVE Rotation
      REMOVE Scale
      REMOVE GDB_GEOMATTR_DATA
      REMOVE PresidentName
      REMOVE Contact
      REMOVE ContactInfo
      REMOVE Notes
      REMOVE _nsupp
    USER_EXPOSED_ATTRIBUTES = Report_No,Supplement_No,Reported_Date,Reported_Time,Location,Map_Coordinates,_todaytimedate,_oneyearfromtoday,Offense,Location_Type,Code,Definition,LocCode,LocationName,_first_match,Address_Anon,_address,_latitude,_longitude,OBJECTID,CITY,NBRHOOD_ID,NAME,COLOR,INSPECTOR,ACTIVE,DIST1,Rotation,Scale,GDB_GEOMATTR_DATA,PresidentName,Contact,ContactInfo,Notes,_nsupp
    -> SpatialRelator_2 [Requestor]
COVID19COUNCILDISTRICTCOUNT (reader MSSQL_SPATIAL_2)
    attributes: OBJECTID integer, ID numeric(38,8), gis_DATA_CouncilDistrict_2011_A numeric(38,8), DISTRICT nvarchar(12), MEMBERS numeric(38,8), LOCKED nvarchar(1), NAME nvarchar(43), POPULATION numeric(38,8), WHITE numeric(38,8), NH_WHT numeric(38,8), NH_WHT1 numeric(38,8), NH_DOJ_BLK numeric(38,8), NH_DOJ_BL1 numeric(38,8), HISPANIC_O numeric(38,8), HISPANIC numeric(38,8), F18_POP numeric(38,8), NH18_WHT numeric(38,8), F18_NH_WHT numeric(38,8), NH18_DOJ_B numeric(38,8), F18_NH_DOJ numeric(38,8), H18_POP numeric(38,8), F18_HISPAN numeric(38,8), DEVIATION numeric(38,8), F_DEVIATIO numeric(38,8), F_18_POP numeric(38,8), F_NH_WHT numeric(38,8), F_NH18_WHT numeric(38,8), F_NH_DOJ_B numeric(38,8), F_HISPANIC numeric(38,8), F_H18_POP numeric(38,8),
      F_NH_WHT1 numeric(38,8), F_NH_DOJ_1 numeric(38,8), F_HISPANI1 numeric(38,8), F_18_NH_WH numeric(38,8), F_NH18_DOJ numeric(38,8), F_18_NH_DO numeric(38,8), F_18_HISPA numeric(38,8), IDEAL_VALU numeric(38,8), F_WHITE numeric(38,8), Point_Count integer, GDB_GEOMATTR_DATA varbinary_max, created_user nvarchar(255), created_date datetime2, last_edited_user nvarchar(255), last_edited_date datetime2
    -> SpatialRelator_2 [Supplier]
SpatialRelator_2
    AGGREGATE_HANDLING = Yes
    ATTR_ACCUM_MODE = Prefix Supplier
    ATTR_PREFIX = cd
    CALC_CARD = No
    CURVE_BOUNDARY_RULE_PARAM = Default Rule
    IGNORE_NULLS = Yes
    PREDICATES = WITHIN
    SUCCESS_ATTR = _cd
    -> AttributeManager_3
AttributeManager_3
    ATTR_TABLE:
      REMOVE cdOBJECTID
      REMOVE cdID
      REMOVE cdgis_DATA_CouncilDistrict_2011_A
      REMOVE cdDISTRICT
      REMOVE cdMEMBERS
      REMOVE cdLOCKED
      RENAME_SET_VALUE cdNAME > CouncilDistrict
      REMOVE cdPOPULATION
      REMOVE cdWHITE
      REMOVE cdNH_WHT
      REMOVE cdNH_WHT1
      REMOVE cdNH_DOJ_BLK
      REMOVE cdNH_DOJ_BL1
      REMOVE cdHISPANIC_O
      REMOVE cdHISPANIC
      REMOVE cdF18_POP
      REMOVE cdNH18_WHT
      REMOVE cdF18_NH_WHT
      REMOVE cdNH18_DOJ_B
      REMOVE cdF18_NH_DOJ
      REMOVE cdH18_POP
      REMOVE cdF18_HISPAN
      REMOVE cdDEVIATION
      REMOVE cdF_DEVIATIO
      REMOVE cdF_18_POP
      REMOVE cdF_NH_WHT
      REMOVE cdF_NH18_WHT
      REMOVE cdF_NH_DOJ_B
      REMOVE cdF_HISPANIC
      REMOVE cdF_H18_POP
      REMOVE cdF_NH_WHT1
      REMOVE cdF_NH_DOJ_1
      REMOVE cdF_HISPANI1
      REMOVE cdF_18_NH_WH
      REMOVE cdF_NH18_DOJ
      REMOVE cdF_18_NH_DO
      REMOVE cdF_18_HISPA
      REMOVE cdIDEAL_VALU
      REMOVE cdF_WHITE
      REMOVE cdPoint_Count
      REMOVE cdGDB_GEOMATTR_DATA
      REMOVE cdcreated_user
      REMOVE cdcreated_date
      REMOVE cdlast_edited_user
      REMOVE cdlast_edited_date
      REMOVE _cd
    USER_EXPOSED_ATTRIBUTES = Code,Definition
    -> AttributeSplitter
AttributeSplitter
    ATTR_NAME = _address
    DELIMITER = ,
    DROP_EMPTY_PARTS = No
    LIST_NAME = _addSplit
    TRIM_OPTION = Both
    -> AttributeManager_4
AttributeManager_4
    ATTR_TABLE:
      RENAME_SET_VALUE _address > REV_Match_addr
      RENAME_SET_VALUE _addSplit{0} > REV_Street
      RENAME_SET_VALUE _addSplit{1} > REV_City = Waco
      RENAME_SET_VALUE _addSplit{2} > REV_Zip
    USER_EXPOSED_ATTRIBUTES = Code,Definition
    -> StringCaseChanger
StringCaseChanger
    ATTRCHOICE = Selected Attributes
    ATTRLIST = REV_City Neighborhood
    CHANGE_TYPE = Full Title Case
    -> Inspector
    -> ReportsLayer (writer ARCGISONLINEFEATURES_2)
ReportsLayer (writer ARCGISONLINEFEATURES_2)
    attributes: OBJECTID OID, Report_No String(12), Reported_Date Date, REV_Street String(100), REV_City String(40), REV_ZIP String(10), REV_Match_addr String(120), ToD String(255), OffenseCommitted String(255), OffenseDef String(512), OffenseAgainst String(512), LocationType String(512), Neighborhood String(40), CouncilDistrict String(43), GlobalID GlobalID(38)
Inspector
