FME workspace energov2 (backup).fmw

Parameters:
- SourceDataset_MSSQL_JDBC_NONSPATIAL_2 = EnergovJDBC   # SQL Server (JDBC) Connection
- SourceDataset_MSSQL_SPATIAL = NTGIS   # SQL Server Connection

Readers:
- MSSQL_JDBC_NONSPATIAL_2_1: MSSQL_JDBC_NONSPATIAL_2 from $(SourceDataset_MSSQL_JDBC_NONSPATIAL_2)
- MSSQL_SPATIAL_1: MSSQL_SPATIAL from $(SourceDataset_MSSQL_SPATIAL)

PMPERMITADDRESS (reader MSSQL_JDBC_NONSPATIAL_2_1)
    attributes: PMPERMITADDRESSID char(36), PMPERMITID char(36), MAILINGADDRESSID char(36), MAIN bit
    -> FeatureMerger_3 [REQUESTOR]
MAILINGADDRESS (reader MSSQL_JDBC_NONSPATIAL_2_1)
    attributes: MAILINGADDRESSID char(36), ADDRESSLINE1 nvarchar(200), ADDRESSLINE2 nvarchar(200), ADDRESSLINE3 nvarchar(200), CITY nvarchar(50), STATE nvarchar(50), COUNTY nvarchar(50), COUNTRY nvarchar(50), POSTALCODE nvarchar(50), COUNTRYTYPE integer, LASTCHANGEDON datetime, LASTCHANGEDBY char(36), POSTDIRECTION nvarchar(30), PREDIRECTION nvarchar(30), ROWVERSION integer, ADDRESSID char(36), ADDRESSTYPE nvarchar(50), STREETTYPE nvarchar(50), PARCELID char(36), PARCELNUMBER nvarchar(50), UNITORSUITE varchar(20), PROVINCE nvarchar(50), RURALROUTE nvarchar(50), STATION nvarchar(50), COMPSITE nvarchar(50), POBOX nvarchar(50), ATTN nvarchar(50), GENERALDELIVERY bit
    -> FeatureMerger_3 [SUPPLIER]
FeatureMerger_3
    ATTR_ACCUM_MODE = Merge Supplier
    ATTR_CONFLICT_RES = Use Requestor
    IGNORE_NULLS = No
    JOIN_KEYS = @Value(MAILINGADDRESSID) @Value(MAILINGADDRESSID) AUTO
    MERGE_TYPE = Attributes Only
    PROCESS_DUPS = NO
    REJECT_NULL_MISSING_KEYS = No
    SUPPLIERS_FIRST = No
    MERGED -> FeatureMerger_4 [SUPPLIER]
PMPERMIT (reader MSSQL_JDBC_NONSPATIAL_2_1)
    attributes: PMPERMITID char(36), PMPERMITSTATUSID char(36), PMPERMITTYPEID char(36), APPLYDATE datetime, EXPIREDATE datetime, PERMITNUMBER nvarchar(50), MAINPERMIT bit, ISSUEDATE datetime, DISTRICTID char(36), PMPERMITWORKCLASSID char(36), IVRNUMBER integer, INTERNALPERMIT bit, KIOSKPERMIT bit, REVIEW bit, CONUMBER nvarchar(50), COISSUEDATE datetime, FINALIZEDATE datetime, LASTINSPECTIONDATE datetime, PLPLANID char(36), STOPWORKORDER bit, USEINSPECTIONPROJECTS bit, NUMBERDWELLINGUNITS integer, SPACIALASSETID char(36), ROWVERSION integer, LASTCHANGEDON datetime, LASTCHANGEDBY char(36), ASSETGEOMETRYCOLLECTIONID char(36), PMPERMITPARENTID char(36), IMPORTCUSTOMFIELDLAYOUTID char(36), VALUE money,
      SQUAREFEET numeric(15,2), DESCRIPTION varchar_max, CALENDARDUEDATE datetime, ISAPPLIEDONLINE bit, CPIVESTEDMAPDATE datetime, OVERRIDEFEEDATE datetime, ASSIGNEDTO char(36)
    -> FeatureJoiner_7 [LEFT]
PMPERMITPARCEL (reader MSSQL_JDBC_NONSPATIAL_2_1)
    attributes: PMPERMITPARCELID char(36), PMPERMITID char(36), PARCELID char(36), MAIN bit, PARCELSPLITPROCESS bit
    -> FeatureJoiner_7 [RIGHT]
FeatureJoiner_7
    ATTR_CONFLICT_RES = Prefer Left
    GEOMETRY_HANDLING = Prefer Left
    JOIN_KEYS = PMPERMITID PMPERMITID AUTO
    JOIN_MODE = Left
    JOINED -> FeatureMerger_4 [REQUESTOR]
FeatureMerger_4
    ATTR_ACCUM_MODE = Merge Supplier
    ATTR_CONFLICT_RES = Use Requestor
    IGNORE_NULLS = No
    JOIN_KEYS = @Value(PMPERMITID) @Value(PMPERMITID) AUTO
    MERGE_TYPE = Attributes Only
    PROCESS_DUPS = NO
    REJECT_NULL_MISSING_KEYS = No
    SUPPLIERS_FIRST = No
    MERGED -> FeatureMerger [REQUESTOR]
PARCEL (reader MSSQL_JDBC_NONSPATIAL_2_1)
    attributes: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
PARCELTAXROLL (reader MSSQL_SPATIAL_1)
    attributes: OBJECTID integer, UPDATE_ID integer, POLYID integer, PROP_ID integer, EXT nvarchar(3), PIN nvarchar(15), GEO_ID nvarchar(50), ABST_CODE nvarchar(10), POLY_AC numeric(38,8), BLOCK_NUM nvarchar(4), LOT_TRACT_NUM nvarchar(4), GRANTEE_DOC nvarchar(70), DEED_TYPE_CD nvarchar(10), CURRENT_DOC nvarchar(25), DATE_DOC datetime2, TILE smallint, MAP nvarchar(20), MAPSCO nvarchar(3), REF_1 nvarchar(60), REF_2 nvarchar(20), REF_ID2 nvarchar(50), EDIT_DT datetime2, CITY_CD nvarchar(6), CNTY_CD nvarchar(6), WATER_DIST_CD nvarchar(6), EXPT_CD nvarchar(8), GRID_ID nvarchar(6), ROTATION smallint, DEED_CD nvarchar(10), SCHOOL_CD nvarchar(6),
      LAND_GRANT_CD nvarchar(10), ZIP_CD nvarchar(5), ZIP_CITY nvarchar(40), LOG_CD nvarchar(10), file_as_name nvarchar(70), pct_ownership numeric(38,8), first_name nvarchar(30), last_name nvarchar(30), dba_name nvarchar(50), addr_line1 nvarchar(60), addr_line2 nvarchar(60), addr_line3 nvarchar(60), addr_city nvarchar(50), addr_state nvarchar(50), addr_zip nvarchar(10), deed_type_cd_1 nvarchar(10), deed_num nvarchar(50), deed_book_id nvarchar(20), deed_book_page nvarchar(20), deed_dt datetime2, updt_dt datetime2, abs_subdv nvarchar(10), abs_subdv_desc nvarchar(60), abs_subdv_ind nvarchar(1), tract_or_lot nvarchar(50), block nvarchar(50), legal_acreage numeric(38,8), legal_desc nvarchar(255), legal_desc_2 nvarchar(255), eff_size_acres numeric(38,8),
      map_id nvarchar(20), ref_id2_1 nvarchar(50), utilities nvarchar(50), topography nvarchar(50), road_access nvarchar(50), zoning nvarchar(50), rgn_cd nvarchar(5), hood_cd nvarchar(10), hood_name nvarchar(50), state_cd nvarchar(10), subset_cd nvarchar(5), ls_table nvarchar(25), land_total_sqft numeric(38,8), land_unit_price numeric(38,8), primary_situs nvarchar(1), situs_num nvarchar(15), situs_street_prefx nvarchar(10), situs_street nvarchar(50), situs_street_sufix nvarchar(10), situs_city nvarchar(30), situs_state nvarchar(2), situs_zip nvarchar(10), situs_display nvarchar(141), bldg_permit_type_cd nvarchar(10), bld_permit_desc nvarchar(50), bldg_permit_issued_to nvarchar(255), bldg_permit_issue_dt datetime2, prop_type_cd nvarchar(5), sl_price numeric(38,8), sl_dt datetime2,
      prop_cmnt nvarchar_max, sl_comment nvarchar_max, appraised_val numeric(38,8), assessed_val numeric(38,8), market numeric(38,8), ref_id1 nvarchar(50), shared_cad_code nvarchar(5), shared_prop_id nvarchar(30), consideration nvarchar(20), prop_val_yr numeric(38,8), MCADPropertyURL nvarchar(150), Description nvarchar(80), RealClassification nvarchar(30), PropID nvarchar(20), Address nvarchar(80), GDB_GEOMATTR_DATA varbinary_max
    -> FeatureMerger [SUPPLIER]
FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(PARCELNUMBER) @Value(PIN) AUTO
    MERGE_TYPE = Attributes and Geometry
    PROCESS_DUPS = YES
    REJECT_NULL_MISSING_KEYS = No
    SUPPLIERS_FIRST = No
    MERGED -> FeatureMerger_2 [REQUESTOR]
PMPERMITSTATUS (reader MSSQL_JDBC_NONSPATIAL_2_1)
    attributes: PMPERMITSTATUSID char(36), NAME nvarchar(50), DESCRIPTION nvarchar_max, HOLDFLAG bit, COMPLETEDFLAG bit, ISSUEDFLAG bit, FAILUREFLAG bit, CANCELLEDFLAG bit, DESCRIPTION_SPANISH nvarchar_max, LASTCHANGEDBY char(36), LASTCHANGEDON datetime, ROWVERSION integer
    -> FeatureMerger_2 [SUPPLIER]
FeatureMerger_2
    ATTR_ACCUM_MODE = Merge Supplier
    ATTR_CONFLICT_RES = Use Requestor
    IGNORE_NULLS = No
    JOIN_KEYS = @Value(PMPERMITSTATUSID) @Value(PMPERMITSTATUSID) AUTO
    MERGE_TYPE = Attributes Only
    PROCESS_DUPS = NO
    REJECT_NULL_MISSING_KEYS = No
    SUPPLIERS_FIRST = No
    MERGED -> AttributeManager
AttributeManager
