FME workspace training001.fmw

Parameters:
- SourceDataset_FILEGDB = C:\Users\Matthew\Downloads\FMEData2020\FMEData2020\Data\Addresses\Addresses.gdb   # File Geodatabase
- DestDataset_SPATIALITE_NATIVE = C:\Users\Matthew\Downloads\FMEData2020\FMEData2020\Output\Training\addresses.sqlite   # SpatiaLite Database

Readers:
- FILEGDB_1: FILEGDB from $(SourceDataset_FILEGDB)

Writers:
- SPATIALITE_NATIVE_1: SPATIALITE_NATIVE to $(DestDataset_SPATIALITE_NATIVE)

PostcodeBoundaries (reader FILEGDB_1)
    attributes: OBJECTID objectid, CFSAUID text(3), SHAPE_Length double, SHAPE_Area double
PostalAddress (reader FILEGDB_1)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> Tester
Tester
    BOOL_OP = OR
    TEST_CLAUSE = TEST @Value(STATUS) = Current
    TEST_MODE = TEST
    PASSED -> SubstringExtractor
SubstringExtractor
    END = 2
    RESULT_ATTR = fsa
    SRC_STRING = @Value(POSTALCODE)
    START = 0
    -> PostalAddress (writer SPATIALITE_NATIVE_1)
PostalAddress (writer SPATIALITE_NATIVE_1)
    attributes: OBJECTID integer, GlobalID text, PSTLADDRESS varchar(250), PSTLCITY varchar(100), PSTLPROV varchar(25), INTSTATE varchar(5), INTPSTLCD varchar(10), COUNTRY varchar(100), REPRESENT varchar(14), STATUS varchar(9), LASTUPDATE text, LASTEDITOR varchar(50), POSTALCODE varchar(6)
